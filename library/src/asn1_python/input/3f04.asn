BHILAIINFO1V2
DEFINITIONS IMPLICIT TAGS ::= BEGIN
Info1FreeReadV2 ::= SEQUENCE {

version INTEGER,
id PrintableString,
validupto PrintableString,
name UTF8String,
dob PrintableString,
uid PrintableString,
emergencyphone UTF8String,
bloodgroup PrintableString,
issuerauthority PrintableString,
gender PrintableString,
dateofissue PrintableString,
designation [0] UTF8String OPTIONAL,
program [1] UTF8String OPTIONAL,
relation [2] PrintableString OPTIONAL,
nameofprimary [3] UTF8String OPTIONAL,
designationofprimary [4] UTF8String OPTIONAL,
programofprimary [5] UTF8String OPTIONAL,
doj [6] PrintableString OPTIONAL,
dojofprimary [7] PrintableString OPTIONAL,
photo OCTET STRING

}
END
